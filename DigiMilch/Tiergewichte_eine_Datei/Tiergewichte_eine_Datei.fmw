FME workspace Tiergewichte_eine_Datei.fmw

Parameters:
- Betriebsnummer =
- DestDataset_POSTGRES_4 =
- DestDataset_POSTGRES_5 =
- SourceDataset_CSV2 =

Readers:
- CSV2_1: CSV2 from $(SourceDataset_CSV2)

Writers:
- POSTGRES_1: POSTGRES to $(DestDataset_POSTGRES_5)
- POSTGRES_2: POSTGRES to $(DestDataset_POSTGRES_4)

Ermittle_Betriebsnummer: SQLCreator
    DATASET = lflgistest
    EXPOSED_ATTRIBUTE_LIST = betrieb_id
    FORMAT = POSTGRES
    POSTGRES_CREATE_FEATURE_TABLES_FROM_DATA = Yes
    POSTGRES_NAMED_CONNECTION = lflgistest
    POSTGRES_QUERY_FEATURE_TYPES_FOR_MERGE_FILTERS = Yes
    POSTGRES_READ_TIME_WITH_TIMEZONE = Yes
    POSTGRES_SCHEMAS_FOR_TABLE_LISTING = digimilch
    SQL_STATEMENT:
      select betrieb_id
      from "digimilch"."betrieb"
      where betriebsnummer = '$(Betriebsnummer)'
    RESULT -> FeatureMerger [SUPPLIER]
Note: 1. Ablauf wird jeden Tag laufen / 2. In DB sind bereits Dateien eingelesen. 3. Um zu verhindern, dass jeden Tag alle Dateien eingelesen werden, wird eine einfache Prüfung durchgeführt: / Datum aus Dateinamen einlesen und mit dem letzten Datum in DB abgleichen
CSV (reader CSV2_1)
    attributes: col0 uint32, col1 uint32, col2 uint32, col3 uint32, col4 varchar(11), col5 varchar(9), col6 varchar(9), col7 time, col8 int32, col9 int32, col10 uint32, col11 uint32
    -> FeatureMerger [REQUESTOR]
Spalten_benennen: AttributeManager
    ATTR_TABLE:
      RENAME_SET_VALUE col0 > stallnummer
      RENAME_SET_VALUE col1 > lom
      RENAME_SET_VALUE col2 > trognummer
      RENAME_SET_VALUE col3 > datum
      RENAME_SET_VALUE col4 > Beginnzeit
      RENAME_SET_VALUE col5 > Endezeit
      RENAME_SET_VALUE col6 > gewicht
      RENAME_SET_VALUE col7 > lfdNr
      REMOVE col8
      REMOVE col9
      SET_TO lom_mit_praefix = DE0@Value(lom)
      SET_TO jjjjmmtt = @Substring(@Value(datum),6,4)@Substring(@Value(datum),3,2)@Substring(@Value(datum),0,2)
    -> LOM_Prüfung__alle_0_und_Dummy_Werte_erkennen_und_weg_
tiergewicht (writer POSTGRES_2)
    attributes: tier_betrieb_id int2,PrimaryKey, standnr int2, besuchsnr int2, datum date, beginn time, ende time, gewicht int4

Bookmark: Dateien, die bereits verarbeitet wurden, werden ausgeschlossen
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Spalten_benennen

Bookmark: fachliche Logik Datensätze mit LOM können schön in DB übertragen werden, bei den anderen wird versucht über die Stalllnummmer die Tier-ID zu ermitteln
LOM_Prüfung__alle_0_und_Dummy_Werte_erkennen_und_weg_: TestFilter
    DEFAULT_VALUE = LOM nicht verfügbar
    TEST_LIST = "BOOL_OP,OR,COMPOSITE_TEST,""""""1"""""",TEST_CLAUSE,TEST @Value(lom) = 0815",dummy ,"BOOL_OP,OR,COMPOSITE_TEST,""""""1"""""",TEST_CLAUSE,TEST @Value(lom) > 0",LOM
    LOM -> LOM__x_Tier.LOM
    LOM nicht verfügbar -> stallnr_x_Tierbetrieb.stallnr_2
Note: Zusatzbedingung - Datum des Wiegens muss zw. Zugang und Abgang liegen
Tester
    BOOL_OP = COMPOSITE
    COMPOSITE_TEST = ( 1 AND 2 ) OR ( 3 AND 4 ) OR  ( 5 AND 6 )
    TEST_CLAUSE:
      TEST @Value(jjjjmmtt) >= @Value(zugang)
      TEST @Value(jjjjmmtt) <= @Value(abgang)
      TEST @Value(jjjjmmtt) >= @Value(zugang)
      TEST abgang ATTRIBUTE_VALUE_NULL ""
      TEST @Value(jjjjmmtt) <= @Value(abgang)
      TEST zugang ATTRIBUTE_VALUE_NULL ""
    TEST_MODE = TEST
    PASSED -> AttributeRenamer
AttributeRenamer
    ATTR_TABLE:
      RENAME_SET_DEFAULT tier_betrieb_id
      RENAME_SET_DEFAULT trognummer > standnr
      RENAME_SET_DEFAULT lfdNr > besuchsnr
      RENAME_SET_DEFAULT jjjjmmtt > datum
      RENAME_SET_DEFAULT Beginnzeit > beginn
      RENAME_SET_DEFAULT Endezeit > ende
      RENAME_SET_DEFAULT Beginngewicht Trog > anfangsgewicht
      RENAME_SET_DEFAULT Endegewicht Trog > endgewicht
    -> DuplicateFilter
DuplicateFilter
    INPUT_ORDERED_CHOICE = No
    KEYATTR = beginn datum tier_betrieb_id
    UNIQUE -> tiergewicht (writer POSTGRES_2)

Bookmark: 1. ermittle Tier-ID über LOM
LOM__x_Tier.LOM: DatabaseJoiner
    ADDED_FIELDS = abgang tier_betrieb_id zugang
    ATTR_ACCUM_MODE = Merge Joined
    ATTR_CONFLICT_RES = Use Original
    CACHE_SIZE = 5000
    DATASET = lflgistest
    FORMAT = POSTGRES
    JOIN_KEYS = lom_mit_praefix lom
    MATCH_MULTIPLE_DISPLAY = Create a feature for each match
    MATCH_RULE_DISPLAY = Match All (1:M)
    POSTGRES_CREATE_FEATURE_TABLES_FROM_DATA = Yes
    POSTGRES_NAMED_CONNECTION = lflgistest
    POSTGRES_QUERY_FEATURE_TYPES_FOR_MERGE_FILTERS = Yes
    POSTGRES_READ_TIME_WITH_TIMEZONE = Yes
    PREFETCH_EXHAUSTIVE = Yes
    TABLE = digimilch.view_tier
    JOINED -> Tester

Bookmark: 2. Wenn LOM nicht vorliegt, dann wirds über Stallnummer versucht
stallnr_x_Tierbetrieb.stallnr_2: DatabaseJoiner
    ADDED_FIELDS = abgang tier_betrieb_id zugang
    ATTR_ACCUM_MODE = Merge Joined
    ATTR_CONFLICT_RES = Use Original
    CACHE_SIZE = 5000
    DATASET = lflgistest
    FORMAT = POSTGRES
    JOIN_KEYS = stallnummer stallnummer
    MATCH_MULTIPLE_DISPLAY = Create a feature for each match
    MATCH_RULE_DISPLAY = Match All (1:M)
    POSTGRES_CREATE_FEATURE_TABLES_FROM_DATA = Yes
    POSTGRES_NAMED_CONNECTION = lflgistest
    POSTGRES_QUERY_FEATURE_TYPES_FOR_MERGE_FILTERS = Yes
    POSTGRES_READ_TIME_WITH_TIMEZONE = Yes
    POSTGRES_SCHEMAS_FOR_TABLE_LISTING = digimilch
    PREFETCH_EXHAUSTIVE = Yes
    TABLE = digimilch.tier_betrieb
    JOINED -> Tester
