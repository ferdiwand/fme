FME workspace Besuchswerte_eine_Datei.fmw

Parameters:
- Betriebsnummer =
- DestDataset_POSTGRES =
- FME_USER_PARAM_PRIVATE_GRP =
- SourceDataset_CSV2 =
- Standort =

Readers:
- CSV2_1: CSV2 from $(SourceDataset_CSV2)

Writers:
- POSTGRES_1: POSTGRES to $(DestDataset_POSTGRES)

CSV (reader CSV2_1)
    attributes: col0 uint32, col1 uint32, col2 uint32, col3 uint32, col4 varchar(11), col5 varchar(9), col6 varchar(9), col7 time, col8 int32, col9 int32, col10 uint32, col11 uint32
    -> FeatureMerger [REQUESTOR]
Ermittle_Betriebsnummer: SQLCreator
    DATASET = lflgistest
    EXPOSED_ATTRIBUTE_LIST = betrieb_id
    FORMAT = POSTGRES
    POSTGRES_CREATE_FEATURE_TABLES_FROM_DATA = Yes
    POSTGRES_NAMED_CONNECTION = lflgistest
    POSTGRES_QUERY_FEATURE_TYPES_FOR_MERGE_FILTERS = Yes
    POSTGRES_READ_TIME_WITH_TIMEZONE = Yes
    POSTGRES_SCHEMAS_FOR_TABLE_LISTING = digimilch
    SQL_STATEMENT:
      select betrieb_id
      from "digimilch"."betrieb"
      where betriebsnummer = '$(Betriebsnummer)'
    RESULT -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Spalten_benennen
Spalten_benennen: AttributeManager
    ATTR_TABLE:
      RENAME_SET_VALUE col0 > stallnummer
      RENAME_SET_VALUE col1 > lom
      RENAME_SET_VALUE col2 > trognummer
      RENAME_SET_VALUE col3 > lfdNr
      RENAME_SET_VALUE col4 > datum
      RENAME_SET_VALUE col5 > Beginnzeit
      RENAME_SET_VALUE col6 > Endezeit
      RENAME_SET_VALUE col7 > gewicht
      RENAME_SET_VALUE col8 > Beginngewicht Trog
      RENAME_SET_VALUE col9 > Endegewicht Trog
      SET_TO jjjjmmtt = @Substring(@Value(datum),6,4)@Substring(@Value(datum),3,2)@Substring(@Value(datum),0,2)
      SET_TO lom_mit_praefix = DE0@Value(lom)
    -> LOM_Prüfung__alle_0_und_Dummy_Werte_erkennen_und_weg_
besuchswerte (writer POSTGRES_1) [off]
    attributes: tier_betrieb_id int2,PrimaryKey, standnr int2, besuchsnr int2, datum date, beginn time, ende time, verzehrsmenge int4, anfangsgewicht int4, endgewicht int4

Bookmark: fachliche Logik Datensätze mit LOM können schön in DB übertragen werden, bei den anderen wird versucht über die Stalllnummmer die Tier-ID zu ermitteln
LOM_Prüfung__alle_0_und_Dummy_Werte_erkennen_und_weg_: TestFilter
    DEFAULT_VALUE = LOM nicht verfügbar
    TEST_LIST = "BOOL_OP,OR,COMPOSITE_TEST,""""""1"""""",TEST_CLAUSE,TEST @Value(lom) = 0815",dummy ,"BOOL_OP,AND,COMPOSITE_TEST,""""""1"""""",TEST_CLAUSE,TEST @Value(lom) > 0",@Value(lom) > 0
    @Value(lom) > 0 -> LOM__x_Tier.LOM
    LOM nicht verfügbar -> stallnr_x_Tierbetrieb.stallnr_2
Note: Zusatzbedingung - Datum des Wiegens muss zw. Zugang und Abgang liegen
Tester
    BOOL_OP = COMPOSITE
    COMPOSITE_TEST = ( 1 AND 2 ) OR ( 3 AND 4 ) OR  ( 5 AND 6 )
    TEST_CLAUSE:
      TEST @Value(jjjjmmtt) >= @Value(zugang)
      TEST @Value(jjjjmmtt) <= @Value(abgang)
      TEST @Value(jjjjmmtt) >= @Value(zugang)
      TEST abgang ATTRIBUTE_VALUE_NULL ""
      TEST @Value(jjjjmmtt) <= @Value(abgang)
      TEST zugang ATTRIBUTE_VALUE_NULL ""
    TEST_MODE = TEST
    PASSED -> AttributeRenamer
AttributeRenamer
    ATTR_TABLE:
      RENAME_SET_DEFAULT trognummer > standnr
      RENAME_SET_DEFAULT lfdNr > besuchsnr
      RENAME_SET_DEFAULT jjjjmmtt > datum
      RENAME_SET_DEFAULT Beginnzeit > beginn
      RENAME_SET_DEFAULT Endezeit > ende
      RENAME_SET_DEFAULT gewicht > verzehrsmenge
      RENAME_SET_DEFAULT Beginngewicht Trog > anfangsgewicht
      RENAME_SET_DEFAULT Endegewicht Trog > endgewicht
    -> DuplicateFilter
DuplicateFilter
    INPUT_ORDERED_CHOICE = No
    KEYATTR = beginn datum tier_betrieb_id
    UNIQUE -> besuchswerte (writer POSTGRES_1)

Bookmark: 1. ermittle Tier-ID über LOM
LOM__x_Tier.LOM: DatabaseJoiner
    ADDED_FIELDS = abgang tier_betrieb_id zugang
    ATTR_ACCUM_MODE = Merge Joined
    ATTR_CONFLICT_RES = Use Original
    CACHE_SIZE = 5000
    DATASET = lflgistest
    FORMAT = POSTGRES
    JOIN_KEYS = lom_mit_praefix lom
    MATCH_MULTIPLE_DISPLAY = Create a feature for each match
    MATCH_RULE_DISPLAY = Match All (1:M)
    POSTGRES_CREATE_FEATURE_TABLES_FROM_DATA = Yes
    POSTGRES_NAMED_CONNECTION = lflgistest
    POSTGRES_QUERY_FEATURE_TYPES_FOR_MERGE_FILTERS = Yes
    POSTGRES_READ_TIME_WITH_TIMEZONE = Yes
    PREFETCH_EXHAUSTIVE = Yes
    TABLE = digimilch.view_tier
    JOINED -> Tester

Bookmark: 2. Wenn LOM nicht vorliegt, dann wirds über Stallnummer versucht
stallnr_x_Tierbetrieb.stallnr_2: DatabaseJoiner
    ADDED_FIELDS = abgang tier_betrieb_id zugang
    ATTR_ACCUM_MODE = Merge Joined
    ATTR_CONFLICT_RES = Use Original
    CACHE_SIZE = 5000
    DATASET = lflgistest
    FORMAT = POSTGRES
    JOIN_KEYS = stallnummer stallnummer betrieb_id betrieb_id
    MATCH_MULTIPLE_DISPLAY = Create a feature for each match
    MATCH_RULE_DISPLAY = Match All (1:M)
    POSTGRES_CREATE_FEATURE_TABLES_FROM_DATA = Yes
    POSTGRES_NAMED_CONNECTION = lflgistest
    POSTGRES_QUERY_FEATURE_TYPES_FOR_MERGE_FILTERS = Yes
    POSTGRES_READ_TIME_WITH_TIMEZONE = Yes
    PREFETCH_EXHAUSTIVE = Yes
    TABLE = digimilch.tier_betrieb
    JOINED -> Tester

FME custom transformer Dateiabgleich - wiegetroege

Parameters:
- LETZTES_DATUM =
- PATH_ROOTNAME =
- PATH_WINDOWS =

AttributeSplitter_Input (input)
    -> AttributeSplitter
AttributeSplitter
    ATTR_NAME = path_rootname
    DELIMITER = _
    DROP_EMPTY_PARTS = Yes
    LIST_NAME = _list
    TRIM_OPTION = Both
    -> FeatureMerger [REQUESTOR]
AttributeManager_2_Input (input)
    -> AttributeManager_2
AttributeManager_2
    ATTR_TABLE:
      SET_TO jahr = @Substring(@Value(letztes_datum),0,4)
      SET_TO monat = @Substring(@Value(letztes_datum),4,2)
      SET_TO tag = @Substring(@Value(letztes_datum),6,2)
    -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Datumvergleich
Datumvergleich: TestFilter
    DEFAULT_VALUE = <UNFILTERED>
    TEST_LIST:
      "BOOL_OP,AND,COMPOSITE_TEST,""""""1 AND 2 AND 3"""""",TEST_CLAUSE,TEST @Value(_list{4}) >= @Value(jahr)
      TEST @Value(_list{5}) >= @Value(monat)
      TEST @Value(_list{6}) > @Value(tag)",zu verarbeitende Dateien
    zu verarbeitende Dateien -> Dateien_einlesen [INITIATOR]
Dateien_einlesen: FeatureReader
    ATTRIBUTES = CSV,"col0,col1,col2,col3,col4,col5,col6,col7,col8,col9"
    ATTR_ACCUM_MODE = Only Use Result
    COMBINE_GEOM = Use Result
    CSV2_CASE_SENSITIVE_FIELD_NAMES = Yes
    CSV2_DATA_START_LINE = 1
    CSV2_DELIMITER = tab
    CSV2_ENCODING = windows-1252
    CSV2_ENFORCE_STRICT_SCHEMA = No
    CSV2_FEATURE_TYPE_NAME = FORMAT_NAME
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 10000
    CSV2_SCAN_TYPES = Yes
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = @Value(path_windows)
    FORMAT = CSV2
    INTERACT = <No Spatial Filter>
    OUTPUT_FEATURES_DISPLAY = Data Features
    CSV -> Dateien_einlesen_CSV (output)
Dateien_einlesen_CSV (output)
